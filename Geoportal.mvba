Attribute VB_Name = "Emapa"
Option Explicit

Public X As Double
Public Y As Double

'====================================
' Główne narzędzie
'====================================
Sub EMapaOdpal()
    Dim PKT1 As CadInputMessage
    Set PKT1 = CadInputQueue.GetInput(msdCadInputTypeDataPoint)
    CadInputQueue.SendCommand "CHOOSE ELEMENT"

    ' przeliczenie współrzędnych na EPSG:2180 (PL-1992)
    Call przelicznik(PKT1.point.Y, PKT1.point.X)

    X = FormatNumber(X, 0)
    Y = FormatNumber(Y, 0)

    Dim url As String
    url = "https://polska.e-mapa.net/?x=" & Y & "&y=" & X & "&zoom=12"

    ' do schowka (opcjonalne)
    On Error Resume Next
    Dim tmpDO As Object
    Set tmpDO = CreateObject("Forms.DataObject")
    tmpDO.SetText url
    tmpDO.PutInClipboard
    On Error GoTo 0

    ' otwarcie w Edge
    CreateObject("Shell.Application").ShellExecute "microsoft-edge:" & url
End Sub

'====================================
' Funkcja przelicznika – wiernie z oryginału
'====================================
Private Sub przelicznik(Xwej As Double, Ywej As Double)
    Dim c132 As Double, c133 As Double
    c132 = Xwej
    c133 = Ywej

    Dim B151 As Integer
    Select Case Left(CStr(Ywej), 1)
        Case "5": B151 = 1
        Case "6": B151 = 2
        Case "7": B151 = 3
        Case "8": B151 = 4
    End Select

    Dim v49 As Double, v50 As Double
    v49 = c132
    v50 = c133

    Dim V30 As Double, V31 As Double, V32 As Double, V33 As Double
    V30 = -8.377321681641E-04
    V31 = -5.905869626083E-08
    V32 = -1.673488904988E-10
    V33 = -2.167737805597E-13

    Dim V21 As Double, V22 As Double, V23 As Double, V24 As Double
    V21 = 0.003356551485597
    V22 = 6.571873148459E-06
    V23 = 1.764656426454E-08
    V24 = 5.40048218776E-11

    Dim I18 As Double, I9 As Double
    I18 = 6367449.14577
    I9 = 0.999923

    Dim I8 As Double
    Select Case B151
        Case 1: I8 = 15
        Case 2: I8 = 18
        Case 3: I8 = 21
        Case 4: I8 = 24
    End Select

    Dim v37 As Double
    Select Case B151
        Case 1: v37 = (v50 - 5500000) / I9
        Case 2: v37 = (v50 - 6500000) / I9
        Case 3: v37 = (v50 - 7500000) / I9
        Case 4: v37 = (v50 - 8500000) / I9
    End Select

    Dim v36 As Double, V35 As Double, V34 As Double
    v36 = v49 / I9
    V35 = v37 / I18
    V34 = v36 / I18

    Dim v29 As Double, v28 As Double, v27 As Double
    v29 = V35 + (V30 * Cos(2 * V34) * SINH(2 * V35) _
                + V31 * Cos(4 * V34) * SINH(4 * V35) _
                + V32 * Cos(6 * V34) * SINH(6 * V35) _
                + V33 * Cos(8 * V34) * SINH(8 * V35))

    v28 = V34 + (V30 * Sin(2 * V34) * COSH(2 * V35) _
                + V31 * Sin(4 * V34) * COSH(4 * V35) _
                + V32 * Sin(6 * V34) * COSH(6 * V35) _
                + V33 * Sin(8 * V34) * COSH(8 * V35))

    v27 = 2 * Atn(Exp(v29)) - Pi() / 2

    Dim V26 As Double, V25 As Double, V14 As Double
    V26 = Atn(Tan(v27) / Cos(v28))
    V25 = ASIN(Cos(v27) * Sin(v28))
    V14 = V25 + V21 * Sin(2 * V25) _
              + V22 * Sin(4 * V25) _
              + V23 * Sin(6 * V25) _
              + V24 * Sin(8 * V25) _
              + 0.0000000008

    Dim V6 As Double, V5 As Double
    V6 = I8 + STOPNIE(V26)
    V5 = STOPNIE(V14)

    ' --- dalsze obliczenia jak w oryginale ---
    Dim J81 As Double, J82 As Double, J83 As Double, J84 As Double
    J81 = RADIANY(V6)
    J82 = RADIANY(V5)
    J83 = RADIANY(V6)
    J84 = RADIANY(19)

    Dim J85 As Double, J86 As Double, J87 As Double, J88 As Double
    J85 = Pi()
    J86 = 6367449.14577
    J87 = 6378137
    J88 = 0.0818191910428

    Dim J93TYM As Double, J93 As Double, J94 As Double
    J93TYM = (((1 - J88 * Sin(J82)) / (1 + J88 * Sin(J82))) ^ (J88 / 2) * Tan(J82 / 2 + J85 / 4))
    J93 = 2 * (Atn(J93TYM) - J85 / 4)
    J94 = J81 - J84

    Dim J96 As Double, J97 As Double
    J96 = Atn(Sin(J93) / (Cos(J93) * Cos(J81 - J84)))
    J97 = 0.5 * Log((1 + Cos(J93) * Sin(J81 - J84)) / (1 - Cos(J93) * Sin(J81 - J84)))

    Dim J98 As Double, J99 As Double, J100 As Double, J101 As Double
    J98 = 8.377318247344E-04
    J99 = 7.608527788826E-07
    J100 = 1.197638019173E-09
    J101 = 2.4433762425E-12

    Dim J104 As Double, J105 As Double
    J104 = J86 * (J96 + (J98 * Sin(2 * J96) * COSH(2 * J97)) _
                        + (J99 * Sin(4 * J96) * COSH(4 * J97)) _
                        + (J100 * Sin(6 * J96) * COSH(6 * J97)) _
                        + (J101 * Sin(8 * J96) * COSH(8 * J97)))

    J105 = J86 * (J97 + (J98 * Cos(2 * J96) * SINH(2 * J97)) _
                        + (J99 * Cos(4 * J96) * SINH(4 * J97)) _
                        + (J100 * Cos(6 * J96) * SINH(6 * J97)) _
                        + (J101 * Cos(8 * J96) * SINH(8 * J97)))

    Dim J117 As Double, J118 As Double
    J117 = 0.9993 * J104 - 5300000
    J118 = 0.9993 * J105 + 500000

    X = J117
    Y = J118
End Sub

'====================================
' Funkcje pomocnicze matematyczne
'====================================
Private Function ASIN(X As Double) As Double
    ASIN = Atn(X / Sqr(-X * X + 1))
End Function

Private Function COSH(X As Double) As Double
    COSH = (Exp(X) + Exp(-X)) / 2
End Function

Private Function SINH(X As Double) As Double
    SINH = (Exp(X) - Exp(-X)) / 2
End Function

Private Function STOPNIE(X As Double) As Double
    STOPNIE = X * 180 / Pi()
End Function

Private Function RADIANY(X As Double) As Double
    RADIANY = X * (Pi() / 180)
End Function

Private Function Pi() As Double
    Pi = 4 * Atn(1)
End Function

Attribute VB_Name = "EmapaRzedna"
Option Explicit

'====================================
'  WysokosciGeoportal.bas  (moduł niezależny – uproszczony)
'====================================

' Stałe konfiguracyjne
Private Const LAYER_CELL As String = "RTPW02 - Punkt wysokościowy_Z GEOPORTALU"
Private Const LAYER_TEXT As String = "RTPW02_O - Punkt wysokościowy_Z GEOPORTALU"
Private Const CELL_NAME  As String = "RTPW02"

Public X As Double   ' EPSG:2180 Northing (N)
Public Y As Double   ' EPSG:2180 Easting  (E)

'------------------------------------
' P U B L I C  E N T R Y
'------------------------------------
Public Sub WysokosciZGeoportalu()
    On Error GoTo EH

    ' 1) Wybór punktu
    Dim PKT1 As CadInputMessage
    Set PKT1 = CadInputQueue.GetInput(msdCadInputTypeDataPoint)
    CadInputQueue.SendCommand "CHOOSE ELEMENT"

    ' 2) Przeliczenie współrzędnych (PL-2000 › EPSG:2180) do X,Y (zaokrąglone)
    przelicznik PKT1.point.Y, PKT1.point.X

    ' 3) Zapytanie do Geoportalu (NMT GetFeatureInfo)
    Dim url As String
    url = "https://mapy.geoportal.gov.pl/wss/ext/NMT/wms?" & _
          "SERVICE=WMS&request=GetFeatureInfo&version=1.1.1" & _
          "&layers=nmt&styles=&srs=EPSG:2180" & _
          "&bbox=" & Y & "," & X & "," & Y & "," & X & _
          "&width=984&height=886&format=image/png&transparent=true" & _
          "&query_layers=nmt&x=496&y=570&INFO_FORMAT=text/html"

    Dim html As String
    html = HttpGetSimple(url)
    Debug.Print (html)
    If Len(html) = 0 Then
        MsgBox "Brak odpowiedzi z Geoportalu (NMT).", vbExclamation
        Exit Sub
    End If

    ' 4) Ekstrakcja wysokości z HTML (np. 163.9)
    Dim hVal As Double
    Debug.Print (hVal)
    hVal = GetHeightSimple(html)
    If hVal = 0 Then
        MsgBox "Nie udało się odczytać wysokości z odpowiedzi serwera.", vbExclamation
        Exit Sub
    End If

    ' 5) Wstaw cell + poziomy napis (zapamiętujemy uchwyt do tekstu)
    Dim txtHorz As TextElement
    Set txtHorz = InsertHeightCellAndText(PKT1.point, hVal)

    ' 6) Drugi klik – kierunek napisu
    ShowPrompt "Wskaż kierunek napisu"
    Dim PKT2 As CadInputMessage
    Set PKT2 = CadInputQueue.GetInput(msdCadInputTypeDataPoint)

    ' 7) Obróć wcześniej wstawiony napis zgodnie z wektorem (PKT1 › PKT2)
    RotateTextInPlace txtHorz, PKT1.point, PKT2.point, hVal

    CommandState.StartDefaultCommand
    Exit Sub

EH:
    MsgBox "WysokosciZGeoportalu: " & err.Description, vbCritical
End Sub

'------------------------------------
' W S T A W I A N I E  E L E M E N T Ó W
'------------------------------------
Private Function InsertHeightCellAndText(pBase As Point3d, ByVal hVal As Double) As TextElement
    Dim p As Point3d, cellScale As Point3d, rot As Matrix3d
    p = pBase: p.Z = hVal
    cellScale = Point3dFromXYZ(0.5, 0.5, 0.5)
    rot = Matrix3dFromAxisAndRotationAngle(2, 0)

    ' Warstwy
    EnsureLevel LAYER_CELL
    EnsureLevel LAYER_TEXT
    Dim lvlCell As Level, lvlText As Level
    Set lvlCell = ActiveDesignFile.Levels(LAYER_CELL)
    Set lvlText = ActiveDesignFile.Levels(LAYER_TEXT)

    ' Spróbuj wstawić cellkę (jeśli brak – nie przerywaj)
    On Error Resume Next
    Dim elCell As element
    Set elCell = Application.CreateCellElement2(CELL_NAME, p, cellScale, True, rot)
    If Not elCell Is Nothing Then
        elCell.Level = lvlCell
        elCell.Color = 0
        ActiveModelReference.AddElement elCell
    Else
        MsgBox "Uwaga: brak cellki '" & CELL_NAME & "' w bibliotece – wstawiam tylko tekst.", vbInformation
    End If
    On Error GoTo 0

    ' Tekst wysokości (poziomo – na razie)
    Dim txt As TextElement
Dim s As String
s = Format$(hVal, "0.0")     ' wymusi jedno miejsce po kropce
s = Replace(s, ",", ".")     ' zamieni przecinek na kropkę
    
    Set txt = CreateTextElement1(Nothing, s, p, rot)
    With txt.TextStyle
        .Justification = msdTextJustificationLeftBottom
        .Height = 0.75
        .Width = 0.65
        .Offset = Point2dFromXY(0.5, 0.5)
        .Color = 0
    End With
    txt.Level = lvlText
    ActiveModelReference.AddElement txt

    Set InsertHeightCellAndText = txt
End Function

Private Sub RotateTextInPlace(ByVal txtHorz As TextElement, p1 As Point3d, p2 As Point3d, ByVal hVal As Double)
    Dim vec As Point3d, rot As Matrix3d
    vec = Point3dSubtract(p2, p1)
    rot = Matrix3dFromRotationBetweenVectors(Point3dFromXYZ(1, 0, 0), vec)

    ' Usuń poprzedni poziomy tekst
    On Error Resume Next
    ActiveModelReference.RemoveElement txtHorz
    On Error GoTo 0

    ' Wstaw nowy – obrócony
    Dim txt As TextElement
    Dim s As String
s = Format$(hVal, "0.0")     ' wymusi jedno miejsce po kropce
s = Replace(s, ",", ".")     ' zamieni przecinek na kropkę
    Set txt = CreateTextElement1(Nothing, s, p1, rot)
    With txt.TextStyle
        .Justification = msdTextJustificationLeftBottom
        .Height = 0.75
        .Width = 0.65
        .Offset = Point2dFromXY(0.5, 0.5)
        .Color = 0
    End With
    txt.Level = ActiveDesignFile.Levels(LAYER_TEXT)
    ActiveModelReference.AddElement txt
End Sub

' Najprostszy parser wysokości z HTML Geoportalu:
' szuka pierwszego " m" i wyciąga liczbę tuż przed nim.
Private Function GetHeightSimple(ByVal html As String) As Double
    Dim lines() As String, ln As String
    Dim i As Long, c As String, onlyNum As String
    
    ' rozbijamy HTML na linie
    lines = Split(html, vbLf)
    
    For i = LBound(lines) To UBound(lines)
        ln = lines(i)
          Debug.Print ln
        ' sprawdź czy w linii jest " m</td>"
        If InStr(1, ln, " m</td>", vbTextCompare) > 0 Then
          
            onlyNum = ""
            
            ' wybieramy tylko cyfry, kropkę i przecinek
            Dim j As Long
            For j = 1 To Len(ln)
                c = Mid$(ln, j, 1)
                If (c >= "0" And c <= "9") Or c = "." Or c = "," Then
                    onlyNum = onlyNum & c
                End If
            Next j
            
            ' zamiana przecinka na kropkę
            onlyNum = Replace(onlyNum, ".", ",")
            
            If IsNumeric(onlyNum) Then
                GetHeightSimple = CDbl(onlyNum)
                Exit Function
            End If
        End If
    Next i
    
    ' jeśli nie znaleziono
    GetHeightSimple = 0#
End Function




'------------------------------------
' H T T P  (proste + awaryjne UTF-8)
'------------------------------------
Private Function HttpGetSimple(ByVal url As String) As String
    On Error GoTo EH
    Dim http As Object
    Set http = CreateObject("MSXML2.XMLHTTP")
    http.Open "GET", url, False
    http.setRequestHeader "User-Agent", "MicroStation-VBA"
    http.Send
    If http.Status = 200 Then
        If Len(http.responseText) > 0 Then
            HttpGetSimple = CStr(http.responseText)
        Else
            ' awaryjna dekodacja UTF-8 z responseBody
            Dim s As Object
            Set s = CreateObject("ADODB.Stream")
            s.Type = 1: s.Open
            s.Write http.responseBody
            s.Position = 0
            s.Type = 2: s.Charset = "utf-8"
            HttpGetSimple = s.ReadText
            s.Close
        End If
    Else
        HttpGetSimple = vbNullString
    End If
    Exit Function
EH:
    HttpGetSimple = vbNullString
End Function

'------------------------------------
' L E V E L E
'------------------------------------
Private Sub EnsureLevel(LevelName As String)
    On Error Resume Next
    Dim lvl As Level
    Set lvl = ActiveDesignFile.Levels(LevelName)
    If lvl Is Nothing Then ActiveDesignFile.AddNewLevel LevelName
    On Error GoTo 0
End Sub

'------------------------------------
' M A T E M A T Y K A  (przelicznik jak w EMapaOdpal)
'   PL-2000 (strefy 5..8) -> PL-1992 (EPSG:2180)
'   USTAWIA globalne X (N), Y (E) – ZAOKRĄGLONE
'------------------------------------
Private Sub przelicznik(Xwej As Double, Ywej As Double)
    Dim c132 As Double, c133 As Double
    c132 = Xwej: c133 = Ywej

    Dim B151 As Integer
    Select Case Left(CStr(Ywej), 1)
        Case "5": B151 = 1
        Case "6": B151 = 2
        Case "7": B151 = 3
        Case "8": B151 = 4
    End Select

    Dim v49 As Double, v50 As Double
    v49 = c132: v50 = c133

    Dim V30 As Double, V31 As Double, V32 As Double, V33 As Double
    V30 = -8.377321681641E-04
    V31 = -5.905869626083E-08
    V32 = -1.673488904988E-10
    V33 = -2.167737805597E-13

    Dim V21 As Double, V22 As Double, V23 As Double, V24 As Double
    V21 = 0.003356551485597
    V22 = 6.571873148459E-06
    V23 = 1.764656426454E-08
    V24 = 5.40048218776E-11

    Dim I18 As Double, I9 As Double
    I18 = 6367449.14577
    I9 = 0.999923

    Dim I8 As Double
    Select Case B151
        Case 1: I8 = 15
        Case 2: I8 = 18
        Case 3: I8 = 21
        Case 4: I8 = 24
    End Select

    Dim v37 As Double
    Select Case B151
        Case 1: v37 = (v50 - 5500000) / I9
        Case 2: v37 = (v50 - 6500000) / I9
        Case 3: v37 = (v50 - 7500000) / I9
        Case 4: v37 = (v50 - 8500000) / I9
    End Select

    Dim v36 As Double, V35 As Double, V34 As Double
    v36 = v49 / I9
    V35 = v37 / I18
    V34 = v36 / I18

    Dim v29 As Double, v28 As Double, v27 As Double
    v29 = V35 + (V30 * Cos(2 * V34) * SINH(2 * V35) _
               + V31 * Cos(4 * V34) * SINH(4 * V35) _
               + V32 * Cos(6 * V34) * SINH(6 * V35) _
               + V33 * Cos(8 * V34) * SINH(8 * V35))

    v28 = V34 + (V30 * Sin(2 * V34) * COSH(2 * V35) _
               + V31 * Sin(4 * V34) * COSH(4 * V35) _
               + V32 * Sin(6 * V34) * COSH(6 * V35) _
               + V33 * Sin(8 * V34) * COSH(8 * V35))

    v27 = 2 * Atn(Exp(v29)) - Pi() / 2

    Dim V26 As Double, V25 As Double, V14 As Double
    V26 = Atn(Tan(v27) / Cos(v28))
    V25 = ASIN(Cos(v27) * Sin(v28))
    V14 = V25 + V21 * Sin(2 * V25) _
              + V22 * Sin(4 * V25) _
              + V23 * Sin(6 * V25) _
              + V24 * Sin(8 * V25) _
              + 0.0000000008

    Dim V6 As Double, V5 As Double
    V6 = I8 + STOPNIE(V26)
    V5 = STOPNIE(V14)

    Dim J81 As Double, J82 As Double, J84 As Double
    J81 = RADIANY(V6)
    J82 = RADIANY(V5)
    J84 = RADIANY(19)

    Dim J85 As Double, J86 As Double, J88 As Double
    J85 = Pi()
    J86 = 6367449.14577
    J88 = 0.0818191910428

    Dim J93TYM As Double, J93 As Double
    J93TYM = (((1 - J88 * Sin(J82)) / (1 + J88 * Sin(J82))) ^ (J88 / 2) * Tan(J82 / 2 + J85 / 4))
    J93 = 2 * (Atn(J93TYM) - J85 / 4)

    Dim J96 As Double, J97 As Double
    J96 = Atn(Sin(J93) / (Cos(J93) * Cos(J81 - J84)))
    J97 = 0.5 * Log((1 + Cos(J93) * Sin(J81 - J84)) / (1 - Cos(J93) * Sin(J81 - J84)))

    Dim J98 As Double, J99 As Double, J100 As Double, J101 As Double
    J98 = 8.377318247344E-04
    J99 = 7.608527788826E-07
    J100 = 1.197638019173E-09
    J101 = 2.4433762425E-12

    Dim J104 As Double, J105 As Double
    J104 = J86 * (J96 + (J98 * Sin(2 * J96) * COSH(2 * J97)) _
                        + (J99 * Sin(4 * J96) * COSH(4 * J97)) _
                        + (J100 * Sin(6 * J96) * COSH(6 * J97)) _
                        + (J101 * Sin(8 * J96) * COSH(8 * J97)))

    J105 = J86 * (J97 + (J98 * Cos(2 * J96) * SINH(2 * J97)) _
                        + (J99 * Cos(4 * J96) * SINH(4 * J97)) _
                        + (J100 * Cos(6 * J96) * SINH(6 * J97)) _
                        + (J101 * Cos(8 * J96) * SINH(8 * J97)))

    Dim J117 As Double, J118 As Double
    J117 = 0.9993 * J104 - 5300000
    J118 = 0.9993 * J105 + 500000

    X = Round(J117, 0)  ' Northing  (Y w e-mapie)
    Y = Round(J118, 0)  ' Easting   (X w e-mapie)
End Sub

'------------------------------------
' M A T H  U T I L S
'------------------------------------
Private Function ASIN(ByVal X As Double) As Double
    ASIN = Atn(X / Sqr(-X * X + 1#))
End Function

Private Function COSH(ByVal X As Double) As Double
    COSH = (Exp(X) + Exp(-X)) / 2#
End Function

Private Function SINH(ByVal X As Double) As Double
    SINH = (Exp(X) - Exp(-X)) / 2#
End Function

Private Function STOPNIE(ByVal X As Double) As Double
    STOPNIE = X * 180# / Pi()
End Function

Private Function RADIANY(ByVal X As Double) As Double
    RADIANY = X * (Pi() / 180#)
End Function

Private Function Pi() As Double
    Pi = 4# * Atn(1#)
End Function

Attribute VB_Name = "v8paletka"
Attribute VB_Base = "0{025B71F9-E981-49B6-AB1B-A2ABA411F953}{B0F6E9F1-E2E2-4359-94FF-BCBA0A9BB857}"
Attribute VB_GlobalNameSpace = False
Attribute VB_Creatable = False
Attribute VB_PredeclaredId = True
Attribute VB_Exposed = False
Attribute VB_TemplateDerived = False
Attribute VB_Customizable = False

Private Sub Image1_BeforeDragOver(ByVal Cancel As MSForms.ReturnBoolean, ByVal Data As MSForms.DataObject, ByVal X As Single, ByVal Y As Single, ByVal DragState As MSForms.fmDragState, ByVal Effect As MSForms.ReturnEffect, ByVal Shift As Integer)

End Sub

Private Sub Image1_Click()
CadInputQueue.SendKeyin "vba run SetStartAngle"
End Sub

Private Sub Image10_Click()
CadInputQueue.SendKeyin "vba run zczytajKilometraz"
End Sub

Private Sub Image11_Click()
CadInputQueue.SendKeyin "vba run AutoRedakcja"
End Sub

Private Sub Image12_Click()
CadInputQueue.SendKeyin "vba run WyrownanieTekstowOdpal"
End Sub

Private Sub Image13_Click()
CadInputQueue.SendKeyin "vba run SzukajLiniOdpal"
End Sub

Private Sub Image14_Click()
CadInputQueue.SendKeyin "level create TNG_4270"
CadInputQueue.SendKeyin "level create TND_4271"
CadInputQueue.SendKeyin "level create RZM"
CadInputQueue.SendKeyin "level create RZM_4276"
CadInputQueue.SendKeyin "level create RZR_4275"
CadInputQueue.SendKeyin "vba run RysujRozjazd"
End Sub

Private Sub Image15_Click()
CadInputQueue.SendKeyin "vba run synchWidoki"
End Sub

Private Sub Image16_Click()
CadInputQueue.SendKeyin "vba run AnalizaToru"
End Sub

Private Sub Image17_Click()
CadInputQueue.SendKeyin "vba run ZwisyOdpal"
End Sub

Private Sub Image18_Click()
CadInputQueue.SendKeyin "vba run PodniesPikieteOdpal"
End Sub

Private Sub Image19_Click()
CadInputQueue.SendKeyin "vba run DodajRzednaWarstwice"
End Sub

Private Sub Image2_Click()
CadInputQueue.SendKeyin "vba run PomocnikPlt"
End Sub

Private Sub Image20_Click()
CadInputQueue.SendKeyin "vba run SzukajTekstuOdpal"
End Sub

Private Sub Image21_Click()
Emapa.EMapaOdpal
End Sub

Private Sub Image22_Click()
CadInputQueue.SendKeyin "vba run WstawOdnosnikOdpal"
End Sub

Private Sub Image23_Click()
EmapaRzedna.WysokosciZGeoportalu
End Sub

Private Sub Image3_Click()
CadInputQueue.SendKeyin "vba run dodaj_punkt"
End Sub

Private Sub Image4_Click()
CadInputQueue.SendKeyin "vba run ExportImport"
End Sub

Private Sub Image5_Click()
CadInputQueue.SendKeyin "vba run WymiarowanieOdpal"
End Sub

Private Sub Image6_Click()
CadInputQueue.SendKeyin "aa=0"
CadInputQueue.SendKeyin "vba run mort"
End Sub

Private Sub Image7_Click()
CadInputQueue.SendKeyin "vba run dodajrzedna"
End Sub

Private Sub Image8_Click()
CadInputQueue.SendKeyin "vba run obrot3d"
End Sub

Private Sub Image9_Click()
CadInputQueue.SendKeyin "vba run Kalkulator"
End Sub
